RFC1155-SMI DEFINITIONS ::= BEGIN

--
-- Node definitions
--
	-- 0
	ccitt OBJECT IDENTIFIER ::= { 0 }

	-- 0.0
	null OBJECT IDENTIFIER ::= { ccitt 0 }

	-- 1
	iso OBJECT IDENTIFIER ::= { 1 }

	-- 1.3
	org OBJECT IDENTIFIER ::= { iso 3 }

	-- 1.3.6
	dod OBJECT IDENTIFIER ::= { org 6 }

	-- 1.3.6.1
	internet OBJECT IDENTIFIER ::= { dod 1 }

	-- 1.3.6.1.1
	directory OBJECT IDENTIFIER ::= { internet 1 }

	-- 1.3.6.1.2
	mgmt OBJECT IDENTIFIER ::= { internet 2 }

	-- 1.3.6.1.3
	experimental OBJECT IDENTIFIER ::= { internet 3 }

	-- 1.3.6.1.4
	private OBJECT IDENTIFIER ::= { internet 4 }

	-- 1.3.6.1.4.1
	enterprises OBJECT IDENTIFIER ::= { private 1 }

END
